module radvd {
  namespace "http://example.com/radvd";
  prefix "radvd";

  import ietf-inet-types {
    prefix "inet";
  }

  description "YANG model for radvd configuration";

  grouping interface-config {
    description "Grouping for interface configuration";

    list interfaces {
      key "instance";
      leaf instance {
        type uint32;
        description "Instance ID";
      }
      leaf name {
        type string;
        description "Interface name";
      }
      leaf adv_send_advert {
        type boolean;
        description "AdvSendAdvert";
        default "true";
      }
      leaf min_rtr_adv_interval {
        type uint32;
        description "MinRtrAdvInterval";
        default "3";
      }
      leaf max_rtr_adv_interval {
        type uint32;
        description "MaxRtrAdvInterval";
        default "10";
      }
      leaf adv_managed_flag {
        type boolean;
        description "AdvManagedFlag";
        default "false";
      }
      leaf adv_other_config_flag {
        type boolean;
        description "AdvOtherConfigFlag";
        default "false";
      }
      leaf adv_default_lifetime {
        type uint32;
        description "AdvDefaultLifetime";
        default "1800";
      }
      leaf adv_default_preference {
        type string;
        description "AdvDefaultPreference";
        default "medium";
      }

      list prefixes {
        key "prefix";
        description "Prefix list";
        leaf prefix {
          type string;
          description "Prefix";
        }
        leaf adv_on_link {
          type boolean;
          description "AdvOnLink";
          default "true";
        }
        leaf adv_autonomous {
          type boolean;
          description "AdvAutonomous";
          default "true";
        }
        leaf adv_router_addr {
          type boolean;
          description "AdvRouterAddr";
          default "true";
        }
        leaf adv_valid_lifetime {
          type uint32;
          description "AdvValidLifetime";
          default "86400";
        }
      }
    
      list rdnss {
        key "address";
        description "RDNSS list";
        leaf address {
          type string;
          description "RDNSS address";
        }
        leaf adv_rdnss_lifetime {
          type uint32;
          description "AdvRDNSSLifetime";
          default "1800";
        }
      }

      list routes {
        key "route";
        description "Route list";
        leaf route {
          type string;
          description "Route";
        }
        leaf adv_route_lifetime {
          type uint32;
          description "AdvRouteLifetime";
          default "300";
        }
        leaf adv_route_preference {
          type string;
          description "AdvRoutePreference";
          default "medium";
        }
      }

      leaf-list clients {
        description "Client list";
        type string;
      }
    }
  }

  rpc start {
    description "Start radvd";

    input {
      uses interface-config;
    }
    output {
      leaf status {
        type string;
        description "Status";
      }
    }
  }
  rpc stop {
    description "Stop radvd";

    input {
      leaf instance {
        type uint32;
        description "Instance ID";
      }
    }
    output {
      leaf status {
        type string;
        description "Status";
      }
    }
  }

  notification update {
    description "Update radvd configuration";
    leaf status {
      type string;
      description "Status";
    }
  }
}
